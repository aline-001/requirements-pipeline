[DOCUMENT]
TITLE: System Elements and Allocation
UID: DOC-ELEMENTS

[GRAMMAR]
ELEMENTS:
- TAG: SECTION
  PROPERTIES:
    IS_COMPOSITE: True
  FIELDS:
  - TITLE: UID
    TYPE: String
    REQUIRED: False
  - TITLE: TITLE
    TYPE: String
    REQUIRED: True
- TAG: ELEMENT
  FIELDS:
  - TITLE: UID
    TYPE: String
    REQUIRED: True
  - TITLE: TITLE
    TYPE: String
    REQUIRED: True
  - TITLE: STATEMENT
    TYPE: String
    REQUIRED: False
  RELATIONS:
  - TYPE: Parent
    ROLE: Implements
  - TYPE: File

[[SECTION]]
TITLE: System elements

[ELEMENT]
UID: ELEM-3
TITLE: Auth Subsystem
STATEMENT: Handles login
RELATIONS:
- TYPE: Parent
  VALUE: REQ-001
  ROLE: Implements
- TYPE: Parent
  VALUE: REQ-004
  ROLE: Implements

[ELEMENT]
UID: ELEM-6
TITLE: Login Component
STATEMENT: Username/password login form and validation

[ELEMENT]
UID: ELEM-7
TITLE: Session Manager
STATEMENT: Tracks active sessions and enforces timeouts
RELATIONS:
- TYPE: Parent
  VALUE: REQ-002
  ROLE: Implements

[ELEMENT]
UID: ELEM-8
TITLE: Password Reset Service
STATEMENT: Handles password reset requests via email

[[/SECTION]]
