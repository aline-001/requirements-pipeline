[DOCUMENT]
TITLE: Secure user login

[SECTION]
TITLE: Stakeholder Need

[REQUIREMENT]
UID: NEED-3
TITLE: Secure user login
STATEMENT: Users must log in securely.
PRIORITY: Must
RATIONALE: Compliance.
STATUS: Approved

[REQUIREMENT]
UID: REQ-004
TITLE: REQ-004
STATEMENT: The system shall authenticate users via SSO
STATUS: Approved
RELATIONS:
- TYPE: Parent
  VALUE: NEED-3
- TYPE: AllocatedTo
  VALUE: Auth Subsystem
- TYPE: VerifiedBy
  VALUE: VER-1
