[DOCUMENT]
TITLE: Session timeout

[SECTION]
TITLE: Stakeholder Need

[REQUIREMENT]
UID: NEED-4
TITLE: Session timeout
STATEMENT: Idle sessions must expire.
PRIORITY: Should
RATIONALE: Security.
STATUS: Approved

[REQUIREMENT]
UID: REQ-002
TITLE: REQ-002
STATEMENT: The system shall expire idle sessions after 15 minutes of inactivity.
STATUS: Approved
RELATIONS:
- TYPE: Parent
  VALUE: NEED-4
- TYPE: AllocatedTo
  VALUE: Login Component
- TYPE: VerifiedBy
  VALUE: VER-2
