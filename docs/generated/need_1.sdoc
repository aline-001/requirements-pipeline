[DOCUMENT]
TITLE: Secure user login

[SECTION]
TITLE: Stakeholder Need

[REQUIREMENT]
UID: NEED-1
TITLE: Secure user login
STATEMENT: Users must be able to log in securely with a username and password.
PRIORITY: Must
RATIONALE: Compliance requirement; user data must be protected.
STATUS: Proposed

[REQUIREMENT]
UID: REQ-004
TITLE: REQ-004
STATEMENT: The system shall authenticate users via SSO in addition to username/password.
STATUS: Approved
RELATIONS:
- TYPE: Parent
  VALUE: NEED-1
